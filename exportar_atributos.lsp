;;; seleccionar_bloques.lsp - Version v0.6.0
;;; Exportación a CSV (separado por ; ) para Excel.
;;; Z deshace último registro y último tramo; polilínea roja única en orden de clics.

(defun SB:STR (v / )
  (cond
    ((= (type v) 'STR) v)
    ((numberp v) (rtos v 2 4))
    ((null v) "")
    (t "")
  )
)

(defun SB:GET-VAL-ATTR (ename tag / e d result encontrado)
  (setq result "" encontrado nil)
  (setq e (entnext ename))
  (while (and e (setq d (entget e)) (/= (cdr (assoc 0 d)) "SEQEND") (not encontrado))
    (if (= (cdr (assoc 0 d)) "ATTRIB")
      (if (= (strcase (cdr (assoc 2 d))) (strcase tag))
        (progn
          (setq result (cdr (assoc 1 d)))
          (setq encontrado t)
        )
      )
    )
    (setq e (entnext e))
  )
  result
)

(defun SB:CARPETA-DESTINO ( / up od dwg cand ruta)
  ;;; Carpeta de salida sin ActiveX:
  ;;; 1) Desktop del usuario, 2) OneDrive\\Desktop, 3) carpeta del dibujo.
  (setq up (getenv "USERPROFILE")
        od (getenv "OneDrive")
        ruta nil)
  (setq cand (list
               (if up (strcat up "\\Desktop") nil)
               (if od (strcat od "\\Desktop") nil)
               (if up (strcat up "\\OneDrive\\Desktop") nil)
             )
  )
  (foreach c cand
    (if (and (null ruta) c (findfile (strcat c "\\")))
      (setq ruta (strcat c "\\"))
    )
  )
  ;; si ninguno confirmó existencia, usar el Desktop habitual igualmente
  (if (null ruta)
    (if (and up (/= up ""))
      (setq ruta (strcat up "\\Desktop\\"))
    )
  )
  (if (null ruta)
    (if (and (setq dwg (getvar "DWGPREFIX")) (/= dwg ""))
      (setq ruta dwg)
    )
  )
  (if (and ruta (/= (substr ruta (strlen ruta)) "\\"))
    (setq ruta (strcat ruta "\\"))
  )
  ruta
)

(defun SB:ARCHIVO-NUEVO (carpeta / i archivo)
  ;;; primer archivo exportado: data_extatt_01.csv, _02, _03, ...
  (setq i 0)
  (while (progn
           (setq i (1+ i))
           (setq archivo (strcat carpeta "data_extatt_"
                          (if (< i 10) "0" "") (itoa i) ".csv"))
           ;;; el bucle continúa mientras el archivo ya exista
           (findfile archivo)
         )
  )
  archivo
)

(defun SB:RUTA-CSV ( )
  ;;; Combina la carpeta de salida con el primer nombre de archivo libre.
  (SB:ARCHIVO-NUEVO (SB:CARPETA-DESTINO))
)

(defun SB:EXPORTAR (data-list / ruta fp idx item ename x y val-e val-sc val-elec val-num val-fat seguir)
  (if (and data-list (> (length data-list) 0))
    (progn
      (setq ruta (SB:RUTA-CSV))
      ;; Si el archivo está bloqueado (abierto en Excel), reintentar al presionar R
      (setq fp nil seguir "R")
      (while (and (eq seguir "R") (null fp))
        (setq fp (open ruta "w"))
        (if (null fp)
          (progn
            (princ (strcat "\n[ERROR] No se pudo escribir en:\n        " ruta "\n"))
            (princ "El archivo puede estar abierto en Excel.\n")
            (initget "S R")
            (setq seguir (getkword "Cerrar Excel y [R]eintentar, o [S]alir? "))
          )
        )
      )
      (if fp
        (progn
          (write-line "No.;Codigo_Poste;Estructura;Circuito;FAT;Coordenada_X;Coordenada_Y" fp)
          (setq idx 0)
          (foreach item data-list
            (setq idx (1+ idx))
            (setq ename (nth 0 item))
            (setq x (nth 2 item))
            (setq y (nth 3 item))
            (setq val-e    (SB:GET-VAL-ATTR ename "E-01"))
            (setq val-sc   (SB:GET-VAL-ATTR ename "SC/H=9M"))
            (setq val-elec (SB:GET-VAL-ATTR ename "01/ELEC/--"))
            (setq val-num  (SB:GET-VAL-ATTR ename "NUMERACION"))
            (setq val-fat  (SB:GET-VAL-ATTR ename "FAT(01)"))
            ;; Si es FAT solo, no imprimir coordenadas
            (if (and (= val-e "") (= val-sc "") (= val-elec "") (= val-num ""))
              (setq x "" y "")
            )
            (write-line
              (strcat (itoa idx) ";"
                      (SB:STR val-e)(SB:STR val-num) ";"
                      (SB:STR val-sc) ";"
                      (SB:STR val-elec) ";"
                      (SB:STR val-fat) ";"
                      (SB:STR x) ";"
                      (SB:STR y))
              fp)
          )
          (close fp)
          (princ "\n================================================")
          (princ "\n¡REPORTE GENERADO CON ÉXITO!")
          (princ (strcat "\nArchivo guardado en:\n        " ruta))
          (princ "\n================================================\n")
        )
        (princ "\nExportación cancelada. No se escribió nada.\n")
      )
    )
    (princ "\n[ERROR] Selección vacía. No se exportó nada.\n")
  )
  (princ)
)

(defun SB:PROCESAR (ename pick / etype edata pt x y px py reg padre)
  (setq px (if pick (car pick) nil)
        py (if pick (cadr pick) nil))
  (setq edata (entget ename))
  (setq etype (SB:STR (cdr (assoc 0 edata))))
  (if (= etype "ATTRIB")
    (progn
      (setq padre (cdr (assoc 330 edata)))
      (if padre (progn (setq ename padre) (setq edata (entget ename)) (setq etype (SB:STR (cdr (assoc 0 edata)))))))
  )
  (if (= etype "INSERT")
    (progn
      (setq pt (cdr (assoc 10 edata)))
      (setq x (if pt (car pt) 0.0))
      (setq y (if pt (cadr pt) 0.0))
      ;; reg: ename, tipo, inserción x/y (para el CSV), clic x/y (para la polilínea)
      (setq reg (list ename "INSERT" x y px py))
    )
  )
  reg
)

(defun SB:CAPLINA ( / nombre ed c)
  ;;; Garantiza la capa roja EXT-ATT-PLINE (la crea o corrige su color).
  (setq nombre "EXT-ATT-PLINE")
  (if (null (tblsearch "LAYER" nombre))
    (entmake (list '(0 . "LAYER")
                   '(100 . "AcDbSymbolTableRecord")
                   '(100 . "AcDbLayerTableRecord")
                   (cons 2 nombre)
                   '(70 . 0)
                   '(62 . 1)
                   '(6 . "Continuous")))
    (progn
      (setq ed (entget (tblobjname "LAYER" nombre)))
      (if (/= (abs (if (setq c (cdr (assoc 62 ed))) c 0)) 1)
        (progn
          (setq ed (subst '(62 . 1) (assoc 62 ed) ed))
          (entmod ed)
        )
      )
    )
  )
)

(defun SB:DIBUJAR-PLINE (data-list pline / pts n ed aux px py)
  ;;; Dibuja/actualiza la polilínea roja.
  (SB:CAPLINA)
  (setq pts nil)
  (foreach reg data-list
    (setq px (nth 4 reg)
          py (nth 5 reg))
    ;; si no hay clic registrado, usar el centro del bloque
    (if (null px) (setq px (nth 2 reg)))
    (if (null py) (setq py (nth 3 reg)))
    (setq pts (cons (list 10 px py) pts))
  )
  (setq pts (reverse pts))
  (setq n (length pts))
  (if (> n 1)
    (if (and pline (= (type pline) 'ENAME) (entget pline))
      (progn
        ;; actualizar vértices conservando su orden
        (setq ed (entget pline)
              aux nil)
        (foreach g ed
          (if (/= (car g) 10)
            (setq aux (cons g aux))
          )
        )
        (setq ed (append (reverse aux) pts))
        (setq ed (subst (cons 90 n) (assoc 90 ed) ed))
        (entmod ed)
        (entupd pline)
        pline
      )
      (progn
        ;; crear la polilínea y tomar su ename con entlast
        (entmake
          (append
            (list '(0 . "LWPOLYLINE")
                  '(100 . "AcDbEntity")
                  '(100 . "AcDbPolyline")
                  '(70 . 0)
                  '(62 . 1)
                  (cons 90 n)
                  (cons 8 "EXT-ATT-PLINE"))
            pts
          )
        )
        (entlast)
      )
    )
    (progn
      ;; 0 o 1 clic: quitar la polilínea de la sesión
      (if (and pline (= (type pline) 'ENAME) (entget pline))
        (entdel pline)
      )
      nil
    )
  )
)

(defun c:EXT-ATT ( / ent reg data-list total val-e val-num val-fat last idx pline)
  (setq data-list nil pline nil)
  (princ "\n------------------------------------------\n")
  (princ "  Extrae Values de bloques y se exporta a excel\n")
  (princ "  ENTER para terminar, Z para invalidar último.\n")
  (princ "--------------------------------------------\n\n")
  
  (while (progn
           (initget "Z")
           (setq ent (entsel "\nSeleccione un bloque o [Z] para Deshacer: "))
        )
    (if (= ent "Z")
      ;; Invalida el último registro mostrando índice y bloque
      (if data-list
        (progn
          (setq last (car (reverse data-list)))        ; último registro
          (setq idx (length data-list))                ; índice actual
          (setq val-e (SB:GET-VAL-ATTR (car last) "E-01"))
          (setq val-num (SB:GET-VAL-ATTR (car last) "NUMERACION"))
          (setq val-fat (SB:GET-VAL-ATTR (car last) "FAT(01)"))
          (princ (strcat "- Eliminado: #" (itoa idx)
                         " - BLQ: " (SB:STR val-e)(SB:STR val-num)(SB:STR val-fat) "\n"))
          ;; quitar último registro y redibujar la polilínea sin el último tramo
          (setq data-list (reverse (cdr (reverse data-list))))
          (setq total (length data-list))
          (setq pline (SB:DIBUJAR-PLINE data-list pline))
        )
        (princ "\nNo hay registros para eliminar.\n")
      )
      ;; Caso normal: registrar bloque
      (progn
        (if (= (cdr (assoc 0 (entget (car ent)))) "LWPOLYLINE")
          ;; La polilínea roja intercepta el clic: re-preguntar sin fallar
          (princ "\nEvite la polilínea roja: pulse sobre el bloque.\n")
          (progn
            (setq reg (SB:PROCESAR (car ent) (cadr ent)))
            (if reg
              (progn
                (setq data-list (append data-list (list reg)))
                (setq total (length data-list))
                ;; Dibujar la polilínea roja con los puntos del clic en orden
                (setq pline (SB:DIBUJAR-PLINE data-list pline))
                ;; Mostrar número y último Value de E-01
                (setq val-e (SB:GET-VAL-ATTR (car reg) "E-01"))
                (setq val-num (SB:GET-VAL-ATTR (car reg) "NUMERACION"))
                (setq val-fat (SB:GET-VAL-ATTR (car reg) "FAT(01)"))
                (princ (strcat "#" (itoa total)
                               " -> BLQ: " (SB:STR val-e)(SB:STR val-num)(SB:STR val-fat) "\n"))
              )
              (princ "\n[ERROR] Selección inválida.\n")
            )
          )
        )
      )
    )
  )
  
  ;; Exportar si hay datos
  (if (and data-list (> (length data-list) 0))
    (SB:EXPORTAR data-list)
    (princ "\n[ERROR] Selección vacía. No se exportó nada.\n")
  )
  
  (princ)
)
