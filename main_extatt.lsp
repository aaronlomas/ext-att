;;; main_extatt.lsp - Version v1.0.0 (archivo unico)

;;; ================================================================
;;; UTILIDADES GENERALES Y LECTURA DE ATRIBUTOS
;;; ================================================================

(defun SB:STR (v / )
  (cond
    ((= (type v) 'STR) v)
    ((numberp v) (rtos v 2 4))
    ((null v) "")
    (t "")
  )
)

(defun SB:GET-VAL-ATTR (ename tag / e d result encontrado)
  (setq result "" encontrado nil)
  (setq e (entnext ename))
  (while (and e (setq d (entget e)) (/= (cdr (assoc 0 d)) "SEQEND") (not encontrado))
    (if (= (cdr (assoc 0 d)) "ATTRIB")
      (if (= (strcase (cdr (assoc 2 d))) (strcase tag))
        (progn
          (setq result (cdr (assoc 1 d)))
          (setq encontrado t)
        )
      )
    )
    (setq e (entnext e))
  )
  result
)

;;; ================================================================
;;; RUTAS - CARPETA DESTINO Y NOMBRE DE ARCHIVO CSV
;;; ================================================================

(defun SB:CARPETA-DESTINO ( / up od dwg cand ruta)
  (setq up (getenv "USERPROFILE")
        od (getenv "OneDrive")
        ruta nil)
  (setq cand (list
               (if up (strcat up "\\Desktop") nil)
               (if od (strcat od "\\Desktop") nil)
               (if up (strcat up "\\OneDrive\\Desktop") nil)
             )
  )
  (foreach c cand
    (if (and (null ruta) c (findfile (strcat c "\\")))
      (setq ruta (strcat c "\\"))
    )
  )
  (if (null ruta)
    (if (and up (/= up ""))
      (setq ruta (strcat up "\\Desktop\\"))
    )
  )
  (if (null ruta)
    (if (and (setq dwg (getvar "DWGPREFIX")) (/= dwg ""))
      (setq ruta dwg)
    )
  )
  (if (and ruta (/= (substr ruta (strlen ruta)) "\\"))
    (setq ruta (strcat ruta "\\"))
  )
  ruta
)

(defun SB:ARCHIVO-NUEVO (carpeta / i archivo)
  (setq i 0)
  (while (progn
           (setq i (1+ i))
           (setq archivo (strcat carpeta "data_extatt_"
                          (if (< i 10) "0" "") (itoa i) ".csv"))
           (findfile archivo)
         )
  )
  archivo
)

(defun SB:RUTA-CSV ( )
  (SB:ARCHIVO-NUEVO (SB:CARPETA-DESTINO))
)

;;; ================================================================
;;; DIBUJO DE POLILINEA ROJA
;;; ================================================================

(defun SB:CAPLINA ( / nombre ed c)
  (setq nombre "EXT-ATT-PLINE")
  (if (null (tblsearch "LAYER" nombre))
    (entmake (list '(0 . "LAYER")
                   '(100 . "AcDbSymbolTableRecord")
                   '(100 . "AcDbLayerTableRecord")
                   (cons 2 nombre)
                   '(70 . 0)
                   '(62 . 1)
                   '(6 . "Continuous")))
    (progn
      (setq ed (entget (tblobjname "LAYER" nombre)))
      (if (/= (abs (if (setq c (cdr (assoc 62 ed))) c 0)) 1)
        (progn
          (setq ed (subst '(62 . 1) (assoc 62 ed) ed))
          (entmod ed)
        )
      )
    )
  )
)

(defun SB:DIBUJAR-PLINE (data-list pline / pts n ed aux px py)
  (SB:CAPLINA)
  (setq pts nil)
  (foreach reg data-list
    (setq px (nth 4 reg)
          py (nth 5 reg))
    (if (null px) (setq px (nth 2 reg)))
    (if (null py) (setq py (nth 3 reg)))
    (setq pts (cons (list 10 px py) pts))
  )
  (setq pts (reverse pts))
  (setq n (length pts))
  (if (> n 1)
    (if (and pline (= (type pline) 'ENAME) (entget pline))
      (progn
        (setq ed (entget pline)
              aux nil)
        (foreach g ed
          (if (/= (car g) 10)
            (setq aux (cons g aux))
          )
        )
        (setq ed (append (reverse aux) pts))
        (setq ed (subst (cons 90 n) (assoc 90 ed) ed))
        (entmod ed)
        (entupd pline)
        pline
      )
      (progn
        (entmake
          (append
            (list '(0 . "LWPOLYLINE")
                  '(100 . "AcDbEntity")
                  '(100 . "AcDbPolyline")
                  '(70 . 0)
                  '(62 . 1)
                  (cons 90 n)
                  (cons 8 "EXT-ATT-PLINE"))
            pts
          )
        )
        (entlast)
      )
    )
    (progn
      (if (and pline (= (type pline) 'ENAME) (entget pline))
        (entdel pline)
      )
      nil
    )
  )
)

;;; ================================================================
;;; DIBUJO DE CIRCULO ROJO (FAT)
;;; ================================================================

(defun SB:DIBUJAR-CIRCULO (pt / nombre ed c)
  (setq nombre "EXT-ATT-CIRCLE")
  (if (null (tblsearch "LAYER" nombre))
    (entmake (list '(0 . "LAYER")
                   '(100 . "AcDbSymbolTableRecord")
                   '(100 . "AcDbLayerTableRecord")
                   (cons 2 nombre)
                   '(70 . 0)
                   '(62 . 1)
                   '(6 . "Continuous")))
    (progn
      (setq ed (entget (tblobjname "LAYER" nombre)))
      (if (/= (abs (if (setq c (cdr (assoc 62 ed))) c 0)) 1)
        (progn
          (setq ed (subst '(62 . 1) (assoc 62 ed) ed))
          (entmod ed)
        )
      )
    )
  )
  (entmake
    (list '(0 . "CIRCLE")
          '(100 . "AcDbEntity")
          '(100 . "AcDbCircle")
          (cons 10 pt)
          '(40 . 7.0)
          '(62 . 1)
          (cons 8 nombre))
  )
  (entlast)
)

;;; ================================================================
;;; PROCESAMIENTO DE ENTIDADES SELECCIONADAS
;;; ================================================================

(defun SB:PROCESAR (ename pick / etype edata pt x y px py reg padre)
  (setq px (if pick (car pick) nil)
        py (if pick (cadr pick) nil))
  (setq edata (entget ename))
  (setq etype (SB:STR (cdr (assoc 0 edata))))
  (if (= etype "ATTRIB")
    (progn
      (setq padre (cdr (assoc 330 edata)))
      (if padre (progn (setq ename padre) (setq edata (entget ename)) (setq etype (SB:STR (cdr (assoc 0 edata)))))))
  )
  (if (= etype "INSERT")
    (progn
      (setq pt (cdr (assoc 10 edata)))
      (setq x (if pt (car pt) 0.0))
      (setq y (if pt (cadr pt) 0.0))
      (setq reg (list ename "INSERT" x y px py 0 0 0))
    )
  )
  reg
)

;;; ================================================================
;;; EXPORTACION A CSV
;;; ================================================================

(defun SB:EXPORTAR (data-list / ruta fp idx item ename x y val-e val-sc val-elec val-num val-fat val-in val-out seguir)
  (if (and data-list (> (length data-list) 0))
    (progn
      (setq ruta (SB:RUTA-CSV))
      (setq fp nil seguir "R")
      (while (and (eq seguir "R") (null fp))
        (setq fp (open ruta "w"))
        (if (null fp)
          (progn
            (princ (strcat "\n[ERROR] No se pudo escribir en:\n        " ruta "\n"))
            (princ "El archivo puede estar abierto en Excel.\n")
            (initget "S R")
            (setq seguir (getkword "Cerrar Excel y [R]eintentar, o [S]alir? "))
          )
        )
      )
      (if fp
        (progn
          (write-line "No.;Codigo_Poste;Estructura;descripcion;FAT;IN;OUT;Coordenada_X;Coordenada_Y" fp)
          (setq idx 0)
          (foreach item data-list
            (setq idx (1+ idx))
            (setq ename (nth 0 item))
            (setq x (nth 2 item))
            (setq y (nth 3 item))
            (setq val-e    (SB:GET-VAL-ATTR ename "E-01"))
            (setq val-sc   (SB:GET-VAL-ATTR ename "SC/H=9M"))
            (setq val-elec (SB:GET-VAL-ATTR ename "01/ELEC/--"))
            (setq val-num  (SB:GET-VAL-ATTR ename "NUMERACION"))
            (setq val-fat  (SB:GET-VAL-ATTR ename "FAT(01)"))
            (setq val-in   (nth 6 item))
            (setq val-out  (nth 7 item))
            (if (and (= val-e "") (= val-sc "") (= val-elec "") (= val-num ""))
              (setq x "" y "")
            )
            (write-line
              (strcat (itoa idx) ";"
                      (SB:STR val-e)(SB:STR val-num) ";"
                      (SB:STR val-sc) ";"
                      (SB:STR val-elec) ";"
                      (SB:STR val-fat) ";"
                      (itoa val-in) ";"
                      (itoa val-out) ";"
                      (SB:STR x) ";"
                      (SB:STR y))
              fp)
          )
          (close fp)
          (princ "\n================================================")
          (princ "\nREPORTE GENERADO CON EXITO!")
          (princ (strcat "\nArchivo guardado en:\n        " ruta))
          (princ "\n================================================\n")
        )
        (princ "\nExportacion cancelada. No se escribio nada.\n")
      )
    )
    (princ "\n[ERROR] Seleccion vacia. No se exporto nada.\n")
  )
  (princ)
)

;;; ================================================================
;;; COMANDO PRINCIPAL: EXT-ATT
;;; ================================================================

(defun c:EXT-ATT ( / ent reg data-list total val-e val-num val-fat val-elec last idx pline toggle-in-out last-reg)
  (setq data-list nil pline nil toggle-in-out 0)
  (princ "\n------------------------------------------\n")
  (princ "  Extrae Values de bloques y se exporta a excel\n")
  (princ "  ENTER para terminar, Z para invalidar ultimo.\n")
  (princ "  Presione 1 para IN/OUT en FAT (+10).\n")
  (princ "--------------------------------------------\n\n")

  (while (progn
           (initget "Z 1")
           (setq ent (entsel "\nSeleccione un bloque, [Z] Deshacer, [1] IN/OUT: "))
        )
    (if (= ent "Z")
      (if data-list
        (progn
          (setq last (car (reverse data-list)))
          (setq idx (length data-list))
          (setq val-e (SB:GET-VAL-ATTR (car last) "E-01"))
          (setq val-num (SB:GET-VAL-ATTR (car last) "NUMERACION"))
          (setq val-fat (SB:GET-VAL-ATTR (car last) "FAT(01)"))
          (setq toggle-in-out (nth 8 last))
          (princ (strcat "- Eliminado: #" (itoa idx)
                         " - BLQ: " (SB:STR val-e)(SB:STR val-num)(SB:STR val-fat) "\n"))
          (setq data-list (reverse (cdr (reverse data-list))))
          (setq total (length data-list))
          (setq pline (SB:DIBUJAR-PLINE data-list pline))
        )
        (princ "\nNo hay registros para eliminar.\n")
      )
      (if (= ent "1")
        (progn
          (if data-list
            (progn
              (setq last-reg (car (reverse data-list)))
              (setq val-fat (SB:GET-VAL-ATTR (car last-reg) "FAT(01)"))
              (if (and val-fat (/= val-fat "") (/= val-fat " "))
                (progn
                  (if (= toggle-in-out 0)
                    (progn
                      (setq last-reg (list (car last-reg) (nth 1 last-reg) (nth 2 last-reg) (nth 3 last-reg) (nth 4 last-reg) (nth 5 last-reg) (+ (nth 6 last-reg) 10) (nth 7 last-reg) 1))
                      (setq data-list (reverse (cons last-reg (cdr (reverse data-list)))))
                      (princ (strcat "\n>> IN: +" (itoa 10) " (Total: " (itoa (nth 6 last-reg)) ") [FAT]\n"))
                    )
                    (progn
                      (setq last-reg (list (car last-reg) (nth 1 last-reg) (nth 2 last-reg) (nth 3 last-reg) (nth 4 last-reg) (nth 5 last-reg) (nth 6 last-reg) (+ (nth 7 last-reg) 10) 0))
                      (setq data-list (reverse (cons last-reg (cdr (reverse data-list)))))
                      (princ (strcat "\n>> OUT: +" (itoa 10) " (Total: " (itoa (nth 7 last-reg)) ") [FAT]\n"))
                    )
                  )
                  (setq toggle-in-out (- 1 toggle-in-out))
                )
                (princ "\nEl ultimo bloque no tiene FAT. Seleccione uno con FAT primero.\n")
              )
            )
            (princ "\nNo hay registros. Seleccione un bloque primero.\n")
          )
        )
        (if (and ent (listp ent))
          (if (= (cdr (assoc 0 (entget (car ent)))) "LWPOLYLINE")
            (princ "\nEvite la polilinea roja: pulse sobre el bloque.\n")
            (progn
              (setq reg (SB:PROCESAR (car ent) (cadr ent)))
              (if reg
                (progn
                  (setq data-list (append data-list (list reg)))
                  (setq total (length data-list))
                  (setq pline (SB:DIBUJAR-PLINE data-list pline))
                  (setq val-e (SB:GET-VAL-ATTR (car reg) "E-01"))
                  (setq val-num (SB:GET-VAL-ATTR (car reg) "NUMERACION"))
                  (setq val-fat (SB:GET-VAL-ATTR (car reg) "FAT(01)"))
                  (setq val-elec (SB:GET-VAL-ATTR (car reg) "01/ELEC/--"))
                  (princ (strcat "#" (itoa total)
                                 " -> BLQ: " (SB:STR val-e)(SB:STR val-num)(SB:STR val-fat) "\n"))
                  (if (and val-fat (/= val-fat "") (/= val-fat " "))
                    (progn
                      (SB:DIBUJAR-CIRCULO (cdr (assoc 10 (entget (car reg)))))
                      (princ (strcat "  [FAT detectado] Circulo rojo dibujado.\n"))
                      (setq toggle-in-out 0)
                    )
                  )
                )
                (princ "\n[ERROR] Seleccion invalida.\n")
              )
            )
          )
        )
      )
    )
  )

  (if (and data-list (> (length data-list) 0))
    (SB:EXPORTAR data-list)
    (princ "\n[ERROR] Seleccion vacia. No se exporto nada.\n")
  )

  (princ)
)
